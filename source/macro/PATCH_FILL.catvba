Attribute VB_Name = "FillIttrations"
Dim AreaOfFill As Double
Dim newForm As UserForm
Sub CATMain()

Dim shell
Set shell = CreateObject("WScript.Shell")

Dim partDocument1 As PartDocument
Set partDocument1 = CATIA.ActiveDocument

Dim part1 As Part
Set part1 = partDocument1.Part

Dim parameters1 As Parameters
Set parameters1 = part1.Parameters
2
Dim hybridShapeFill1 As HybridShapeFill
If partDocument1.Selection.Count = 0 Or partDocument1.Selection.Count > 1 Then
MsgBox "Invalid Selection"
Exit Sub
End If

Set hybridShapeFill1 = partDocument1.Selection.Item(1).Value

Dim x
Dim A
Dim inc As Double

UserForm_FillIttrations.Show
If UserForm_FillIttrations.OptionButton1.Enabled Then
inc = 0.002
Else
inc = 0.005
End If

Set A = CreateObject("Scripting.Dictionary")
hybridShapeFill1.AdvancedTolerantMode = 3
hybridShapeFill1.MaximumDeviationValue = inc
x = hybridShapeFill1.MaximumDeviationValue
CATIA.RefreshDisplay = True

Dim c
Dim i As Integer
Dim myArray()

'Row,Column
ReDim myArray(1 To 2, 1 To 1)
i = 1

Do
    rows = UBound(myArray, 1) - LBound(myArray, 1) + 1
    cols = UBound(myArray, 2) - LBound(myArray, 2) + 1
    'Debug.Print rows & "-" & cols

    x = x + inc
    hybridShapeFill1.MaximumDeviationValue = x
    On Error Resume Next
    part1.UpdateObject hybridShapeFill1
    On Error GoTo 0
    shell.Run "powershell -command ""Start-Sleep -Milliseconds 50""", 0, True
    CATIA.RefreshDisplay = True

    getArea hybridShapeFill1
    CATIA.StatusBar = x
    ' Resize array to add a new row BEFORE assigning
    ReDim Preserve myArray(1 To 2, 1 To i)
    myArray(1, i) = AreaOfFill
    myArray(2, i) = x

    i = i + 1
    If x > 0.1 Then Exit Do
Loop

Error:
k = 0
Dim smallest
Dim smallestIndex
col1 = UBound(myArray, 2) - LBound(myArray, 2) + 1
For k = 1 To col1
On Error Resume Next
If myArray(1, k) < myArray(1, k - 1) Then
smallest = myArray(1, k)
smallestIndex = myArray(2, k)
End If
Next k

hybridShapeFill1.MaximumDeviationValue = smallestIndex
part1.UpdateObject hybridShapeFill1
MsgBox "Done"
End Sub


Sub getArea(obj)
Dim activePart As PartDocument
Set activePart = CATIA.ActiveDocument
    Set SPAWorkbench = activePart.GetWorkbench("SPAWorkbench")
    Set Reference = activePart.Part.CreateReferenceFromGeometry(obj)

    CATIA.RefreshDisplay = True
    Dim measurable ' As measurable
    Set measurable = SPAWorkbench.GetMeasurable(Reference)
    On Error GoTo Error:
    AreaOfFill = measurable.area
    Exit Sub
    
Error:
AreaOfFill = 10000000000000#
End Sub

Attribute VB_Name = "TAP_SIZE_IN_DRG"
Sub CATMain()
Dim drawingDocument1 As DrawingDocument
Set drawingDocument1 = CATIA.ActiveDocument

Dim drawingSheets1 As DrawingSheets
Set drawingSheets1 = drawingDocument1.Sheets

Dim drawingSheet1 As DrawingSheet
Set drawingSheet1 = drawingSheets1.Item("A4 TEMPLATE")

Dim drawingViews1 As DrawingViews
Set drawingViews1 = drawingSheet1.Views

Dim drawingDimensions1 As DrawingDimensions
Set drawingDimensions1 = drawingViews1.Item("Bottom view")

Dim drawingDimension1 As DrawingDimension

Dim boolean1 As Boolean
boolean1 = drawingDimension1.Forshortened

'Set drawingDimension2 = drawingDimensions1.Item("Dimension.6")
Set drawingDimension1 = drawingDocument1.Selection.Item(1).Value

drawingDimension1.DimType

End Sub

Attribute VB_Name = "UserForm_FillIttrations"
Attribute VB_Base = "0{635EC892-9462-4F70-BD89-E3D8C42769DC}{38F35A4F-AFDF-4214-91B7-92EA5BCC4754}"
Attribute VB_GlobalNameSpace = False
Attribute VB_Creatable = False
Attribute VB_PredeclaredId = True
Attribute VB_Exposed = False
Attribute VB_TemplateDerived = False
Attribute VB_Customizable = False
Private Sub CommandButton1_Click()
Me.Hide
End Sub
Private Sub UserForm_QueryClose(Cancel As Integer, CloseMode As Integer)
    If CloseMode = vbFormControlMenu Then
        End
    End If
End Sub

Attribute VB_Name = "createExtent"
'Macro created by Maneesh Babu, maneeshbabu6@gmail.com 01-04-2025
#If Win64 Then
    Declare PtrSafe Sub cSleep Lib "\\192.1.52.1\j2ds\Design\Design Users\MANEESH\can delete\STP\stp\wait64.dll" (ByVal dwMilliseconds As Long)
#Else
    Declare Sub cSleep Lib "\\192.1.52.1\j2ds\Design\Design Users\MANEESH\can delete\STP\stp\wait32.dll" (ByVal dwMilliseconds As Long)
#End If

Const BM_CLICK As Long = &HF5
Private Declare PtrSafe Function FindWindow Lib "user32" Alias "FindWindowA" (ByVal lpClassName As String, ByVal lpWindowName As String) As LongPtr
Private Declare PtrSafe Function FindWindowEx Lib "user32" Alias "FindWindowExA" (ByVal hWndParent As LongPtr, ByVal hWndChildAfter As LongPtr, ByVal lpszClass As String, ByVal lpszWindow As String) As LongPtr
Private Declare PtrSafe Function SendMessage Lib "user32" Alias "SendMessageA" (ByVal hWnd As LongPtr, ByVal wMsg As Long, ByVal wParam As Long, ByVal lParam As Long) As Long
Sub CATMain()
Dim shell
Set shell = CreateObject("WScript.Shell")

Dim partDocument1 As PartDocument
Set partDocument1 = CATIA.ActiveDocument

Dim sel As Selection
Set sel = CATIA.ActiveDocument.Selection

Dim selc As Collection
Set selc = New Collection

Dim i As Integer
Dim flag As Integer
i = 0
For i = 1 To sel.Count
selc.add sel.Item(i)
Next i

Dim part1 As Part
Set part1 = partDocument1.Part

Dim orderedGeometricalSets1 As OrderedGeometricalSets
Set orderedGeometricalSets1 = part1.OrderedGeometricalSets

Dim orderedGeometricalSet1 As OrderedGeometricalSet
Set orderedGeometricalSet1 = orderedGeometricalSets1.add()
orderedGeometricalSet1.Name = "EXT"

'-----------------------------------------------------
'disassemble
sel.Remove 2
CATIA.StartCommand "Disassemble"
CATIA.RefreshDisplay = True
cSleep 1000
CATIA.RefreshDisplay = True
ClickOkOnPopup "Disassemble", "ok"
cSleep 1000
'-----------------------------------------------------
'create join
Dim curves As Collection
Set curves = New Collection

repeate:

Dim hybridShapes1 As HybridShapes
Set hybridShapes1 = orderedGeometricalSet1.HybridShapes

Dim hybridShapeFactory1 As HybridShapeFactory
Set hybridShapeFactory1 = part1.HybridShapeFactory


If flag = 0 Then
  For Each ele In orderedGeometricalSet1.HybridShapes
  curves.add ele
  Next ele
  flag = 1
End If

Dim ref1 As Reference
Dim ref2 As Reference
Set ref1 = curves.Item(1)
Set ref2 = Nothing

Dim hybridShapeAssemble1 As HybridShapeAssemble
Set hybridShapeAssemble1 = hybridShapeFactory1.AddNewJoin(ref1, ref2)
On Error Resume Next
orderedGeometricalSet1.InsertHybridShape hybridShapeAssemble1

part1.InWorkObject = hybridShapeAssemble1

part1.Update
On Error GoTo 0
'-----------------------------------------------------

Dim reference1 As Reference
Set reference1 = part1.CreateReferenceFromObject(hybridShapeAssemble1)

Dim bodies1 As Bodies
Set bodies1 = part1.Bodies

Dim body1 As Body
Set body1 = bodies1.Item("PartBody")

Dim hybridShapes2 As HybridShapes
Set hybridShapes2 = body1.HybridShapes

Dim hybridShapeExtractMulti1 As HybridShapeExtractMulti
Set hybridShapeExtractMulti1 = selc.Item(2).Value

Dim reference2 As Reference
Set reference2 = part1.CreateReferenceFromObject(hybridShapeExtractMulti1)

Dim hybridShapeExtrapol1 As HybridShapeExtrapol
Set hybridShapeExtrapol1 = hybridShapeFactory1.AddNewExtrapolLength(reference1, reference2, 50#)

hybridShapeExtrapol1.BorderType = 1

hybridShapeExtrapol1.SetAssemble True

hybridShapeExtrapol1.PropagationMode = 0

hybridShapeExtrapol1.ExtendEdgesMode = False

hybridShapeExtrapol1.ConstantLengthMode = False

hybridShapeExtrapol1.SetContinuityType 1, 0

orderedGeometricalSet1.InsertHybridShape hybridShapeExtrapol1

part1.InWorkObject = hybridShapeExtrapol1

part1.Update
Dim x1
x1 = 1
ReDim indexForRemove(curves.Count) As Integer

For Each ele In curves
  On Error Resume Next
  x1 = x1 + 1
  indexForRemove(x1) = x1
  hybridShapeAssemble1.AddElement ele
  part1.UpdateObject hybridShapeExtrapol1
  If Err.Number <> 0 Then
    Err.Clear
    hybridShapeAssemble1.RemoveElement x1
    part1.UpdateObject hybridShapeExtrapol1
    If Err.Number > 0 Then Exit For
    Exit For
  End If
  
Next ele

For i = 1 To x1
If curves.Count > 0 Then curves.Remove 1
Next i

If curves.Count > 0 Then
GoTo repeate:
End If

End Sub
Sub ClickOkOnPopup(popupTitle As String, buttonName As String)
    Dim hPopup As LongPtr
    Dim hButton As LongPtr

    hPopup = FindWindow(vbNullString, popupTitle)
    If hPopup = 0 Then
        MsgBox "Popup window not found. Check that the popup is open and the title is correct."
        Exit Sub
    End If

    hButton = FindWindowEx(hPopup, 0, "Button", buttonName)
    If hButton = 0 Then
        MsgBox buttonName & " button not found on the popup."
        Exit Sub
    End If

    SendMessage hButton, BM_CLICK, 0, 0
End Sub

Attribute VB_Name = "delete_old_patch_rmv_chf"
Sub CATMain()
On Error Resume Next
Dim partDocument1 As PartDocument
Set partDocument1 = CATIA.ActiveDocument

Dim sel As Selection
Set sel = CATIA.ActiveDocument.Selection

sel.Clear
sel.Search "CATPrtSearch.RemoveFace,all"
sel.Delete
sel.Clear
sel.Search "CATPrtSearch.Chamfer,all"
sel.Delete
sel.Clear
sel.Search "CATPrtSearch.ConstantEdgeFillet,all"
sel.Delete
sel.Clear
sel.Search "CATPrtSearch.Thickness,all"
sel.Delete
sel.Clear

End Sub

Attribute VB_Name = "extentIttration"
Sub CATMain()

Dim partDocument1 As PartDocument
Set partDocument1 = CATIA.ActiveDocument

Dim part1 As Part
Set part1 = partDocument1.Part

Dim ext As HybridShapeExtrapol
Dim l As Length
If partDocument1.Selection.Count = 0 Or partDocument1.Selection.Count > 1 Then
MsgBox "Invalid Selection"
Exit Sub
End If

Set ext = partDocument1.Selection.Item(1).Value
Set l = ext.Length
Dim x As Integer

On Error Resume Next

For x = 50 To 1 Step -1
  Err.Clear
  l.Value = x
  part1.UpdateObject ext
  CATIA.StatusBar = x
  If Err.Number = 0 Then Exit Sub
  
Next x

End Sub

Attribute VB_Name = "hideShowWindows"
' Declare Windows API functions
Declare PtrSafe Function FindWindow Lib "user32" Alias "FindWindowA" ( _
    ByVal lpClassName As String, _
    ByVal lpWindowName As String) As LongPtr

Declare PtrSafe Function ShowWindow Lib "user32" ( _
    ByVal hWnd As LongPtr, _
    ByVal nCmdShow As Long) As Long
    
Declare PtrSafe Function SetForegroundWindow Lib "user32" ( _
    ByVal hWnd As LongPtr) As Long

Declare PtrSafe Function SetCursorPos Lib "user32" ( _
    ByVal x As Long, _
    ByVal y As Long) As Long

Declare PtrSafe Sub mouse_event Lib "user32" ( _
    ByVal dwFlags As Long, _
    ByVal dx As Long, _
    ByVal dy As Long, _
    ByVal cButtons As Long, _
    ByVal dwExtraInfo As Long)
    
' Constants for ShowWindow
Const SW_MAXIMIZE = 3
Const SW_MINIMIZE = 6
Const SW_RESTORE = 9
Const MOUSEEVENTF_LEFTDOWN = &H2
Const MOUSEEVENTF_LEFTUP = &H4

Sub MaximizeWindow(windowTitle)
    Dim hWnd As LongPtr
    hWnd = FindWindow(vbNullString, windowTitle) ' Change to your target window title
    If hWnd <> 0 Then
        ShowWindow hWnd, SW_MAXIMIZE
    Else
        MsgBox "Window not found!"
    End If
End Sub


Sub MinimizeWindow(windowTitle)
    Dim hWnd As LongPtr
    hWnd = FindWindow(vbNullString, windowTitle) ' Change to your target window title
    If hWnd <> 0 Then
        ShowWindow hWnd, SW_MINIMIZE
    Else
        MsgBox "Window not found!"
    End If
End Sub


Sub RestoreWindow(windowTitle)
    Dim hWnd As LongPtr
    hWnd = FindWindow(vbNullString, windowTitle) ' Replace with your target window title
    If hWnd <> 0 Then
        ShowWindow hWnd, SW_RESTORE
    Else
        MsgBox "Window not found!"
    End If
End Sub


Sub BringWindowToFront(windowTitle)
    Dim hWnd As LongPtr
    hWnd = FindWindow(vbNullString, windowTitle) ' Replace with your target window title
    If hWnd <> 0 Then
        ShowWindow hWnd, SW_RESTORE ' Restore if minimized
        SetForegroundWindow hWnd   ' Bring to front
    Else
        MsgBox "Window not found!"
    End If
End Sub
Sub MaximizeAndClickTopLeft(windowTitle)
    Dim hWnd As LongPtr
    hWnd = FindWindow(vbNullString, windowTitle) ' Replace with your target window title

    If hWnd <> 0 Then
        ShowWindow hWnd, SW_MAXIMIZE
        SetForegroundWindow hWnd
        Dim shell
        Set shell = CreateObject("WScript.Shell")
        shell.Run "powershell -command ""Start-Sleep -Milliseconds 1000""", 0, True

        ' Move cursor to top-left and click
        SetCursorPos 0, 0
        mouse_event MOUSEEVENTF_LEFTDOWN, 0, 0, 0, 0
        mouse_event MOUSEEVENTF_LEFTUP, 0, 0, 0, 0
    Else
        MsgBox "Window not found!"
    End If
End Sub

Sub CATMain()
'Dim shell
'Set shell = CreateObject("WScript.Shell")
'shell.Run "powershell -command ""Start-Sleep -Milliseconds 500""", 0, True

'MaximizeWindow "Automatic backup not available when session launched with -macro option."
'shell.Run "powershell -command ""Start-Sleep -Milliseconds 500""", 0, True
MinimizeWindow "Automatic backup not available when session launched with -macro option."
'shell.Run "powershell -command ""Start-Sleep -Milliseconds 500""", 0, True
'MaximizeAndClickTopLeft "Automatic backup not available when session launched with -macro option."
End Sub

Attribute VB_Name = "patchFill"
Sub CATMain()
    Dim partDocument1 As PartDocument
    Set partDocument1 = CATIA.ActiveDocument

    Dim part1 As Part
    Set part1 = partDocument1.Part

    Dim bodies1 As Bodies
    Set bodies1 = part1.Bodies
    Dim obj As Variant

    Dim body1 As Body
    'Set body1 = bodies1.Item("PartBody")
    Set obj = getActiveBody()
    Set body1 = bodies1.Item(obj.Name)
    
    Dim sel
    Set sel = CATIA.ActiveDocument.Selection
    
    'Debug.Print body1.Name
    
    ' Create sketch
    Dim sketches1 As Sketches
    Set sketches1 = body1.Sketches

    Dim reference1 As Reference
    Set reference1 = sel.Item(1).Value

    Dim sketch1 As Sketch
    Set sketch1 = sketches1.add(reference1)

    sketch1.InverseOrientation

    Dim arrayOfVariantOfDouble1(8)
    arrayOfVariantOfDouble1(0) = 0#
    arrayOfVariantOfDouble1(1) = 0#
    arrayOfVariantOfDouble1(2) = 215#
    arrayOfVariantOfDouble1(3) = 1#
    arrayOfVariantOfDouble1(4) = 0#
    arrayOfVariantOfDouble1(5) = 0#
    arrayOfVariantOfDouble1(6) = 0#
    arrayOfVariantOfDouble1(7) = 1#
    arrayOfVariantOfDouble1(8) = 0#

    Set sketch1Variant = sketch1
    sketch1Variant.SetAbsoluteAxisData arrayOfVariantOfDouble1

    part1.InWorkObject = sketch1

    Dim factory2D1 As Factory2D
    Set factory2D1 = sketch1.OpenEdition()

    Dim geometricElements2 As GeometricElements
    Set geometricElements2 = factory2D1.CreateProjections(reference1)

    sketch1.CloseEdition
    part1.InWorkObject = body1
    part1.Update

    ' Create pad
    part1.InWorkObject = body1

    Dim shapeFactory1 As ShapeFactory
    Set shapeFactory1 = part1.ShapeFactory

    Dim pad1 As Pad
    Set pad1 = shapeFactory1.AddNewPad(sketch1, 120#)
    pad1.Name = "autoPatchFill"

    Dim limit1 As Limit
    Set limit1 = pad1.FirstLimit
    limit1.LimitMode = catUpToPlaneLimit

    'Dim body2 As Body
    'Set body2 = bodies1.Item("Body.3")

    'Dim shapes2 As Shapes
    'Set shapes2 = body2.Shapes

    'Dim pad2 As Pad
    'Set pad2 = shapes2.Item("Pad.1")

    ' Up to face
    Dim reference3 As Reference
    Set reference3 = sel.Item(2).Value
    limit1.LimitingElement = reference3

    part1.Update
End Sub
Function getActiveBody() As AnyObject
Dim obj As Variant
Set obj = CATIA.ActiveDocument.Part.InWorkObject

Dim i As Integer
Do
'Debug.Print obj.Name
i = i + 1
  'On Error Resume Next
  If TypeName(obj) = "Body" Then
    Exit Do
  End If
  Set obj = obj.Parent
  
  If i > 10 Then Exit Do
Loop

Set getActiveBody = obj

End Function

Attribute VB_Name = "runMacroModule"
Sub CATMain()

runMacro "D:\OneDrive - JBM Group\Macro\PATCH_FILL.catvba", "Module1", "Text"

End Sub


Sub runMacro(path As String, moduleName As String, functionName As String)

Dim isMacroExist As Boolean
Dim fileName As String
Dim arrInitial As Variant
Dim arr As Variant
Dim params() As Variant
Dim cat

params = Array()
Set cat = CATIA

On Error GoTo ErrorHandle:
Set settingControllers1 = CATIA.settingControllers
Dim macrosSettingAtt1 ' As MacrosSettingAtt
Set macrosSettingAtt1 = settingControllers1.Item("CATScriptMacrosSettingCtrl")

arrInitial = macrosSettingAtt1.GetDefaultMacroLibraries()

For Each macroPath In arrInitial
  If macroPath = path Then
  isMacroExist = True
  Exit For
  End If
Next

If isMacroExist <> True Then
  Dim array1
  ReDim array1(0)
  array1(0) = path
  macrosSettingAtt1.SetDefaultMacroLibraries array1
End If

cat.SystemService.ExecuteScript path, catScriptLibraryTypeVBAProject, moduleName, functionName, params
Exit Sub

ErrorHandle:
MsgBox Err.Description

End Sub
Sub Text()
MsgBox "run sucess"
End Sub

Attribute VB_Name = "updateAnythingInAllParts"
Sub CATMain()
Dim val
val = InputBox("Value ?")

Dim itmName: itmName = CATIA.ActiveDocument.Selection.Item(1).Value.Name
'Debug.Print TypeName(CATIA.ActiveDocument.Selection.Item(1).Value)
Dim sel As Selection
Set sel = CATIA.ActiveDocument.Selection
If sel.Count = 0 Then Exit Sub

'sel.Search "(Name=" & itmName & " & (((CATStFreeStyleSearch.Plane + CATPrtSearch.Plane) + CATGmoSearch.Plane) + CATSpdSearch.Plane)),all"
sel.Search "Name=" & itmName & ",all"
Dim pln As HybridShapePlaneOffset
Dim hol As Hole

Dim i As Integer
i = 0

On Error Resume Next
If TypeName(CATIA.ActiveDocument.Selection.Item(1).Value) = "HybridShapePlaneOffset" Then
  For i = 1 To sel.Count
    Set pln = sel.Item(i).Value
    pln.Offset.Value = val
  Next i
End If

If TypeName(CATIA.ActiveDocument.Selection.Item(1).Value) = "Hole" Then
  For i = 1 To sel.Count
    Set hol = sel.Item(i).Value
    hol.HeadDepth.Value = val
  Next i
End If

End Sub
