Attribute VB_Name = "mesure"
Sub CATMain()



part1.Update

Dim documents1 As Documents
Set documents1 = CATIA.Documents

Dim productDocument1 As ProductDocument
Set productDocument1 = documents1.Item("_MSIL_YTB-MC_62126_REINF_REAR_FLR_SIDE_MBR_NO1_R_PC-04046_BLANKING.CATProduct")

Dim product1 As Product
Set product1 = productDocument1.Product

Dim products1 As Products
Set products1 = product1.Products

Set Nothing1 = products1.Item("19-02-2024")



Dim bodies1 As Bodies
Set bodies1 = part1.Bodies

Dim body1 As Body
Set body1 = bodies1.Item("PAD REMOVE BODY")

Dim shapes1 As Shapes
Set shapes1 = body1.Shapes

Dim pocket1 As Pocket
Set pocket1 = shapes1.Item("Pocket.4")

Dim reference1 As Reference
Set reference1 = part1.CreateReferenceFromBRepName("FEdge:(Edge:(Face:(Brp:(Pocket.4;0:(Brp:(Sketch.82;9)));None:();Cf11:());Face:(Brp:(Pocket.4;0:(Brp:(Sketch.82;10)));None:();Cf11:());None:(Limits1:();Limits2:());Cf11:());WithTemporaryBody;WithoutBuildError;WithInitialFeatureSupport;MFBRepVersion_CXR15)", pocket1)

Dim constraint1 As Constraint
Set constraint1 = constraints1.AddMonoEltCst(catCstTypeLength, reference1)

constraint1.Mode = catCstModeDrivenDimension

'constraint1.SetConstraintVisuLocation -126.019997, 289.909241, -93.853345

End Sub

Attribute VB_Name = "search"
Sub CATMain()

Dim partDocument1 As PartDocument
Set partDocument1 = CATIA.ActiveDocument

Dim selection1 As Selection
Set selection1 = partDocument1.Selection

sel.search "Topology.CGMEdge,sel"

End Sub

Attribute VB_Name = "search2"
Sub CATMain()

Dim partDocument1 As PartDocument
Set partDocument1 = CATIA.ActiveDocument

Dim selection1 As Selection
Set selection1 = partDocument1.Selection

selection1.search "Topology.CGMEdge,sel"

End Sub

Attribute VB_Name = "selectSimilarEdge"
Sub CATMain()
Dim edge1 As Edge
Dim sel As Selection
Dim obj As AnyObject
Dim refLength As Double
Dim constraint1 As Constraint
Dim partDocument1 As PartDocument
Dim part1 As Part
Dim constraints1 As Constraints
Dim i As Integer

Set sel = CATIA.ActiveDocument.Selection

If sel.Count > 0 Then
Set edge1 = sel.Item(1).Value
Else
MsgBox "select edge first"
Exit Sub
End If

Set partDocument1 = CATIA.ActiveDocument
Set part1 = partDocument1.Part
Set constraints1 = part1.Constraints
Set constraint1 = constraints1.AddMonoEltCst(catCstTypeLength, edge1)

constraint1.Mode = catCstModeDrivenDimension

refLength = constraint1.Dimension.Value

Set obj = edge1.Parent

sel.Clear
sel.Add obj

sel.search "Topology.CGMEdge,sel"

On Error Resume Next

For i = 1 To sel.Count
Set constraint1 = constraints1.AddMonoEltCst(catCstTypeLength, sel.Item(i))
constraint1.Mode = catCstModeDrivenDimension

If constraint1.Dimension.Value <> refLength Then
sel.Remove i
End If
Next i

End Sub
