Attribute VB_Name = "DIM_SIZE_2_5MM"
Sub CATMain()

Dim drawingDocument1 As DrawingDocument
Set drawingDocument1 = CATIA.ActiveDocument

Dim Sheets1 As DrawingSheets
Set Sheets1 = drawingDocument1.Sheets

Dim Sheet1 As DrawingSheet
Set Sheet1 = Sheets1.ActiveSheet

Dim views1 As DrawingViews
Set views1 = Sheet1.Views

Dim dims1 As DrawingDimensions
Dim dim1 As DrawingDimension

Dim sel1 As Selection
Set sel1 = drawingDocument1.Selection

For X = 1 To views1.Count
  If views1.Item(X).Name <> "Main View" Or views1.Item(X).Name <> "Background View" Then
    Set dims1 = views1.Item(X)
      For i = 1 To dims1.Count
        Set dim1 = dims1.Item(i)
        sel1.Add dim1
      Next i
    End If
Next X

End Sub

Attribute VB_Name = "UPDATE_ALL_SHEETS"
Sub CATMain()

Dim drawingDocument1 As DrawingDocument
Set drawingDocument1 = CATIA.ActiveDocument

Dim drawingSheets1 As DrawingSheets
Set drawingSheets1 = drawingDocument1.Sheets

Dim drawingSheet1 As DrawingSheet

For i = 1 To drawingSheets1.Count
drawingSheets1.Item(i).Update
Next i
MsgBox "Updated All Sheets"

End Sub

Attribute VB_Name = "rec"
Sub CATMain()

Dim drawingDocument1 As DrawingDocument
Set drawingDocument1 = CATIA.ActiveDocument

Dim drawingSheets1 As DrawingSheets
Set drawingSheets1 = drawingDocument1.Sheets

Dim drawingSheet1 As DrawingSheet
Set drawingSheet1 = drawingSheets1.Item("08")

Dim drawingViews1 As DrawingViews
Set drawingViews1 = drawingSheet1.Views

Dim drawingDimensions1 As DrawingDimensions
Set drawingDimensions1 = drawingViews1.Item("Front view")

Dim drawingDimension1 As DrawingDimension
Set drawingDimension1 = drawingDimensions1.Item("Dimension.1")

Dim boolean1 As Boolean
boolean1 = drawingDimension1.Forshortened

Dim boolean2 As Boolean
boolean2 = drawingDimension1.Forshortened

Dim boolean3 As Boolean
boolean3 = drawingDimension1.Forshortened

Dim boolean4 As Boolean
boolean4 = drawingDimension1.Forshortened

Dim boolean5 As Boolean
boolean5 = drawingDimension1.Forshortened

End Sub
