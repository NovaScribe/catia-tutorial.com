Attribute VB_Name = "mainModule"
'solid
Dim chf As Chamfer
Dim radi As ConstRadEdgeFillet

'surface
Dim eFillet As ConstRadEdgeFillet
Dim sFillet As HybridShapeFilletBiTangent
Dim extent As HybridShapeExtrapol

Sub CATMain()
Dim doc As Document
Set doc = CATIA.ActiveDocument

Dim sel As Selection
Set sel = doc.Selection

'close if not proper selection
If sel.Count <> 1 Then
Exit Sub
End If

Dim objType As String
objType = GetType(sel.Item(1).Value)

inputsize = InputBox("Required Side ?")

Dim obj
If objType = Chamfer Then
Do
    On Error Resume Next
    Debug.Print size1
    size1 = size1 - 1
    CATIA.Application.RefreshDisplay = True
    fillet2.Radius.Value = size1
    part1.Update
    DoEvents
Loop Until (Err.Number = 0 Or size1 = 1)
On Error GoTo 0
Next X
End Sub

Function GetType(obj) As String
On Error Resume Next

If Err.Number = 0 Then
Set chf = obj
If Err.Number = 0 Then GetType = "Chamfer"
End If

If Err.Number = 13 Then
Err.Clear
Set radi = obj
If Err.Number = 0 Then GetType = "ConstRadEdgeFillet"
End If

If Err.Number = 13 Then
Err.Clear
Set eFillet = obj
If Err.Number = 0 Then GetType = "ConstRadEdgeFillet"
End If

If Err.Number = 13 Then
Err.Clear
Set sFillet = obj
If Err.Number = 0 Then GetType = "HybridShapeFilletBiTangent"
End If

If Err.Number = 13 Then
Err.Clear
Set extent = obj
If Err.Number = 0 Then GetType = "Extent"
End If

If Err.Number = 13 Then
GetType = "None"
End If

End Function
