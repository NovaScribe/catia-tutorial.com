Attribute VB_Name = "Client"
Sub CATMain()
UserForm1.Show
End Sub

Attribute VB_Name = "UserForm1"
Attribute VB_Base = "0{A796CBC2-DDE9-423E-A3EB-550B729307F1}{A5A038AE-52AA-44C4-A6B6-0C00ACA62A05}"
Attribute VB_GlobalNameSpace = False
Attribute VB_Creatable = False
Attribute VB_PredeclaredId = True
Attribute VB_Exposed = False
Attribute VB_TemplateDerived = False
Attribute VB_Customizable = False

' Constants for Windows API functions
Private Const AF_INET As Long = 2
Private Const SOCK_STREAM As Long = 1
Private Const IPPROTO_TCP As Long = 6
Private Const INVALID_SOCKET As Long = -1
Private Const SOCKET_ERROR As Long = -1
Private Const WSAGetLastError As Long = &H2736
 
Private Declare PtrSafe Function WSAStartup Lib "ws2_32.dll" (ByVal wVersionRequested As Long, lpWSAData As wsaData) As Long
Private Declare PtrSafe Function WSACleanup Lib "ws2_32.dll" () As Long
Private Declare PtrSafe Function socket Lib "ws2_32.dll" (ByVal af As Long, ByVal socktype As Long, ByVal protocol As Long) As Long
Private Declare PtrSafe Function connect Lib "ws2_32.dll" (ByVal s As Long, SOCKADDR As SOCKADDR, ByVal namelen As Long) As Long
Private Declare PtrSafe Function send Lib "ws2_32.dll" (ByVal s As Long, ByVal buf As String, ByVal buflen As Long, ByVal flags As Long) As Long
Private Declare PtrSafe Function closesocket Lib "ws2_32.dll" (ByVal s As Long) As Long
 
Private Type wsaData
    wVersion As Integer
    wHighVersion As Integer
    szDescription(0 To 255) As Byte
    szSystemStatus(0 To 128) As Byte
    iMaxSockets As Integer
    iMaxUdpDg As Integer
    lpVendorInfo As Long
End Type
 
Private Type SOCKADDR
    sin_family As Integer
    sin_port As Integer
    sin_addr As Long
    sin_zero(0 To 7) As Byte
End Type
 
Private Declare PtrSafe Function inet_addr Lib "ws2_32.dll" (ByVal cp As String) As Long
Private Sub CommandButton1_Click()
UserForm1.TextBox2.Value = GetFilePathAndName
End Sub

Function GetFilePathAndName()

  Dim fs As FileSystem
  Set fs = FileSystem

Dim filePath As String
filePath = fs.OpenFileDialog("Select File", "*.*")

GoTo Skip:

    Dim fDialog As FileSystem
    Dim selectedFile As String
    Dim fso As Object
    Dim filePath As String
    Dim fileName As String
    
    ' Initialize FileDialog
    Set fDialog = Application.fileDialog(msoFileDialogFilePicker)
    Set fso = CreateObject("Scripting.FileSystemObject")
    
    ' Configure the FileDialog
    With fDialog
        .Title = "Select a File"
        .Filters.Clear
        .Filters.Add "All Files", "*.*"
        .AllowMultiSelect = False
        
        ' Show the dialog and capture the selected file
        If .Show = -1 Then
            selectedFile = .SelectedItems(1)
            
            ' Get the file details using FSO
            filePath = fso.GetParentFolderName(selectedFile)
            fileName = fso.GetFileName(selectedFile)
            
            ' Display the results
            GetFilePathAndName = filePath & "\" & fileName
        Else
            MsgBox "No file was selected.", vbExclamation, "File Selection"
        End If
    End With
    
    ' Cleanup
    Set fDialog = Nothing
    Set fso = Nothing
    
Skip:
    GetFilePathAndName = filePath
End Function

Private Sub CommandButton2_Click()
Dim portValue As Variant
portValue = Val(UserForm1.TextBox1.Value)

If Not IsNumeric(portValue) Or portValue < 1600 Or portValue > 1900 Then
    MsgBox "Invalid port number. Please enter a valid port (1600-1650).", vbCritical, "Error"
    Exit Sub
End If

If UserForm1.TextBox2.Value <> "" Then
ExampleTCPClient (UserForm1.TextBox2.Value)
Else
MsgBox "check etails again", vbOKOnly, "Error"
End If
End Sub


 
' Function to initialize Winsock
Private Function InitWinsock() As Boolean
    Dim wsaData As wsaData
    If WSAStartup(&H202, wsaData) = 0 Then
        InitWinsock = True
    Else
        MsgBox "Failed to initialize Winsock."
        InitWinsock = False
    End If
End Function
 
' Function to create a TCP socket and connect to a server
Private Function ConnectToServer(ByVal serverIP As String, ByVal Port As Integer) As Long
    Dim s As Long
    Dim serverAddr As SOCKADDR
    
    ' Create socket
    s = socket(AF_INET, SOCK_STREAM, IPPROTO_TCP)
    If s <> INVALID_SOCKET Then
        ' Set up server address
        serverAddr.sin_family = AF_INET
        serverAddr.sin_addr = inet_addr(serverIP) ' Convert IP address to network byte order
        serverAddr.sin_port = htons(Port) ' Convert port to network byte order
        
        ' Connect to server
        If connect(s, serverAddr, Len(serverAddr)) = 0 Then
            ConnectToServer = s ' Return socket handle
        Else
            MsgBox "Failed to connect to server."
            'MsgBox "Failed to connect to server. Error code: " & WSAGetLastError(), vbCritical
            ConnectToServer = 0
        End If
    Else
        MsgBox "Failed to create socket."
        ConnectToServer = 0
    End If
End Function
 
' Function to send data over a socket
Private Function SendData(ByVal s As Long, ByVal data As String) As Boolean
    If send(s, data, Len(data), 0) <> SOCKET_ERROR Then
        SendData = True
    Else
        MsgBox "Failed to send data."
        SendData = False
    End If
End Function
 
' Function to clean up Winsock
Private Sub CleanupWinsock()
    If WSACleanup() <> 0 Then
        MsgBox "Failed to clean up Winsock."
    End If
End Sub
 
' Function to convert IP address string to network byte order
Private Function htons(ByVal hostshort As Integer) As Integer
    Dim b1 As Integer
    Dim b2 As Integer
    b1 = hostshort And &HFF
    b2 = (hostshort And &HFF00) \ &H100
    htons = (b1 * &H100) + b2
End Function
 
' Function to handle errors
Private Function HandleError() As String
    Dim errMsg As String
    Dim errCode As Long
    errCode = WSAGetLastError()
    errMsg = "Winsock error: " & errCode
    HandleError = errMsg
End Function
 
' Example usage
Sub ExampleTCPClient(n As String)
    Dim serverIP As String
    Dim Port As Integer
    Dim socketHandle As Long
    Dim dataToSend As String
    Dim success As Boolean
    
    ' Initialize Winsock
    If InitWinsock() Then
        ' Set server IP and port
        serverIP = "192.1.52.118"
        Port = UserForm1.TextBox1.Value
        
        ' Connect to server
        socketHandle = ConnectToServer(serverIP, Port)
        If socketHandle <> 0 Then
            ' Data to send
            dataToSend = n
            
            ' Send data
            success = SendData(socketHandle, dataToSend)
            If success Then
                MsgBox "Data sent successfully."
            Else
                MsgBox "Failed to send data."
            End If
            
            ' Close socket
            closesocket socketHandle
        End If
        
        ' Clean up Winsock
        CleanupWinsock
    End If
End Sub


Private Sub UserForm_Initialize()
Me.TextBox1.Value = 1600
End Sub
