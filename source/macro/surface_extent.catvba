Attribute VB_Name = "HIDE_PART"
Sub CATMain()

Dim productDocument1 As ProductDocument
Set productDocument1 = CATIA.ActiveDocument

Dim selection1 As Selection
Set selection1 = productDocument1.Selection

'selection1.Search "((((((CATProductSearch.Part + CATStFreeStyleSearch.PartFeature) + CATAsmSearch.Part) + CATPrtSearch.PartFeature) + CATGmoSearch.PartFeature) + CATSpdSearch.PartFeature) + CATPcsSearch.Part),all"

'selection1.Search "((CATProductSearch.Part + CATStFreeStyleSearch.PartFeature) + CATAsmSearch.Part)"

Dim visPropertySet1 As VisPropertySet
Set visPropertySet1 = selection1.VisProperties

'selection2.Add selection1.Item(1).Value

Set visPropertySet1 = visPropertySet1.Parent

Dim showStatus As Boolean
showStatus = visPropertySet1.GetShow(catVisPropertyShowAttr)
showStatus = visPropertySet1.GetShow(catVisPropertyNoShowAttr)

visPropertySet1.SetShow 0
Exit Sub
If showStatus Then
visPropertySet1.SetShow 0
Else
visPropertySet1.SetShow 1
End If
'selection2.Clear

End Sub

Attribute VB_Name = "SURFACEeXTENT"
#If Win64 Then
    Declare PtrSafe Sub cSleep Lib "\\192.1.52.1\j2ds\Design\Design Users\MANEESH\can delete\STP\stp\wait64.dll" (ByVal dwMilliseconds As Long)
#Else
    Declare Sub cSleep Lib "\\192.1.52.1\j2ds\Design\Design Users\MANEESH\can delete\STP\stp\wait32.dll" (ByVal dwMilliseconds As Long)
#End If
Sub CATMain()
CATIA.RefreshDisplay = True

Dim xlength As Double
xlength = InputBox("Extent Length")

Dim partDocument1 As PartDocument
Set partDocument1 = CATIA.ActiveDocument

Dim part1 As Part
Set part1 = partDocument1.Part

Dim orderedGeometricalSets1 As OrderedGeometricalSets
Set orderedGeometricalSets1 = part1.OrderedGeometricalSets

'create ordered geometry
Dim orderedGeometricalSet1 As OrderedGeometricalSet
Set orderedGeometricalSet1 = orderedGeometricalSets1.Add()

orderedGeometricalSet1.Name = "Extended_Surface"

part1.Update
'-------------------------------------------------------------

Dim hybridShapeFactory1 As HybridShapeFactory
Set hybridShapeFactory1 = part1.HybridShapeFactory

Dim reference1 As Reference
Dim obj As AnyObject
If CATIA.ActiveDocument.Selection.Count <> 0 Then
Set reference1 = CATIA.ActiveDocument.Selection.Item(1).Value
Else
MsgBox "select any face of surface or Part"
Exit Sub
End If

'creating extract
Dim hybridShapeExtract1 As HybridShapeExtract
Set hybridShapeExtract1 = hybridShapeFactory1.AddNewExtract(reference1)

hybridShapeExtract1.PropagationType = 2

hybridShapeExtract1.ComplementaryExtract = False

hybridShapeExtract1.IsFederated = False

orderedGeometricalSet1.InsertHybridShape hybridShapeExtract1

part1.InWorkObject = hybridShapeExtract1

part1.Update


'creating new boundary
Dim reference2 As Reference
Set reference2 = part1.CreateReferenceFromObject(hybridShapeExtract1)

Dim hybridShapeBoundary1 As HybridShapeBoundary
Set hybridShapeBoundary1 = hybridShapeFactory1.AddNewBoundaryOfSurface(reference2)

Dim hybridShapePointCoord1 As HybridShapePointCoord
Dim pointref As Reference
Set pointref = CATIA.ActiveDocument.Selection.Item(2).Value
Set hybridShapePointCoord1 = hybridShapeFactory1.AddNewPointCoord(0#, 0#, 0#)
hybridShapePointCoord1.PtRef = pointref
orderedGeometricalSet1.InsertHybridShape hybridShapePointCoord1

part1.InWorkObject = hybridShapePointCoord1

'Dim reference3 As Reference
'Set reference3 = CATIA.ActiveDocument.Selection.Item(2).Value

hybridShapeBoundary1.From = hybridShapePointCoord1

hybridShapeBoundary1.FromOrientation = 1

orderedGeometricalSet1.InsertHybridShape hybridShapeBoundary1

part1.InWorkObject = hybridShapeBoundary1

part1.Update
CATIA.ActiveDocument.Selection.Clear
CATIA.RefreshDisplay = True
part1.Update
CATIA.ActiveDocument.Selection.Add hybridShapeBoundary1
CATIA.StartCommand ("Disassemble")
UserForm1.Show
cSleep (500)

Dim hybridShapeExtrapol1 As HybridShapeExtrapol
Dim reference4 As Reference
Dim reference5 As Reference

Dim strArray() As String
Dim x As Integer

x = 0
CATIA.RefreshDisplay = True

CATIA.RefreshDisplay = True
CATIA.ActiveDocument.Selection.Clear
part1.Update


Dim totalItems As Integer
totalItems = orderedGeometricalSet1.HybridShapes.Count


'creating extend
For i = 3 To totalItems
On Error Resume Next

Set reference4 = orderedGeometricalSet1.HybridShapes.Item(i)
Set hybridShapeExtrapol1 = hybridShapeFactory1.AddNewExtrapolLength(reference4, hybridShapeExtract1, xlength)
hybridShapeExtrapol1.BorderType = 1
hybridShapeExtrapol1.SetAssemble False
hybridShapeExtrapol1.PropagationMode = 0
hybridShapeExtrapol1.ExtendEdgesMode = False
hybridShapeExtrapol1.ConstantLengthMode = False
hybridShapeExtrapol1.SetContinuityType 2, 0
orderedGeometricalSet1.InsertHybridShape hybridShapeExtrapol1
part1.InWorkObject = hybridShapeExtrapol1
part1.UpdateObject hybridShapeExtrapol1

CATIA.ActiveDocument.Selection.Clear
CATIA.ActiveDocument.Selection.Add hybridShapeExtrapol1
CATIA.StartCommand ("Reframe On")

If Err.Number <> 0 Then
x = x + 1
strArray(x) = hybridShapeExtrapol1.Name
ReDim Preserve strArray(1 To 50 + x)
Err.Clear
End If

On Error GoTo 0
Next i

CATIA.ActiveDocument.Selection.Clear
Y = 0

For Y = 1 To 200
Debug.Print strArray(Y)
On Error Resume Next
CATIA.ActiveDocument.Selection.Add part1.FindObjectByName(strArray(Y))
Next Y

CATIA.RefreshDisplay = True
UserForm1.Show
CATIA.ActiveDocument.Selection.Delete
MsgBox "Done", vbOKOnly
End Sub

Attribute VB_Name = "UserForm1"
Attribute VB_Base = "0{2D6F39F8-6DD7-4BCA-B07B-4E5AFAD0A3B1}{51F125B6-CF63-43FF-98C5-A539CCBB5488}"
Attribute VB_GlobalNameSpace = False
Attribute VB_Creatable = False
Attribute VB_PredeclaredId = True
Attribute VB_Exposed = False
Attribute VB_TemplateDerived = False
Attribute VB_Customizable = False
Private Sub CommandButton1_Click()
Me.Hide
End Sub
