Attribute VB_Name = "stp_path_test"
Sub CATMain()
Dim file_s As Object
Set file_s = CATIA.FileSystem.GetFolder("\\192.1.52.1\j2ds\Design\Design Users\MANEESH\can delete\STP\stp").Files

Dim stpFileFiltered As Collection
Set stpFileFiltered = getStpFiles(file_s)

For Each obj In stpFileFiltered
Debug.Print obj.Path
Next obj

End Sub

Function getStpFiles(file_s As Object) As Collection
For i = 1 To file_s.Count

If VBA.Mid(file_s.Item(i).Name, InStrRev(file_s.Item(i).Name, ".") + 1) = "stp" Or VBA.Mid(file_s.Item(i).Name, InStrRev(file_s.Item(i).Name, ".") + 1) = "step" Then

Dim stpFiles As Collection
Set stpFiles = New Collection
stpFiles.Add file_s.Item(i)
End If

Next i

Set getStpFiles = stpFiles

End Function
