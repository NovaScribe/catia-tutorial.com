Attribute VB_Name = "Module1"
Sub CATMain()

On Error GoTo catch:
Dim partDoc As PartDocument
Dim part1 As part

Set partDoc = CATIA.ActiveDocument
Set part1 = partDoc.part

Dim incValue As Double
incValue = InputBox("Increment Value , Ex : 1  , 2  , 5")

Dim sketch1 As Sketch
If partDoc.Selection.Count = 0 Then
'MsgBox "Select Sketch"
Set sketch1 = partDoc.part.InWorkObject
Else
Set sketch1 = partDoc.Selection.Item(1).Value
End If

'Set sketch1 = partDoc.Selection.Item(1).Value

Dim constrains1 As Constraints
Set constrains1 = sketch1.Constraints

Dim constrain1 As Constraint
Dim i As Integer, increment As Integer
Dim x As Integer
x = 0
For x = 1 To constrains1.Count
Debug.Print constrains1.Item(x).Name
Next x

'InputBox("Increment Value , Ex : 1  , 2  , 5")

For i = 1 To constrains1.Count
increment = 0

Do While constrains1.Item(i).Dimension.Value > increment
Debug.Print "Actual   :  " & constrains1.Item(i).Dimension.Value & "   VS  " & increment
Debug.Print constrains1.Item(i).Dimension.Value - increment
If constrains1.Item(i).Dimension.Value - increment >= incValue / 2 Or constrains1.Item(i).Dimension.Value - increment < incValue Then
increment = increment + incValue
ElseIf constrains1.Item(i).Dimension.Value = increment Then
Exit For
End If
increment = increment + 1
Loop
constrains1.Item(i).Dimension.Value = increment
Next i
part1.Update
Exit Sub

catch:
  If Err.Description = "Type mismatch" Then
    MsgBox "Error : " & Err.Description
    Debug.Print Err.Description
  End If
  
End Sub
