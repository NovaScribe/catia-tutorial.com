Attribute VB_Name = "Module1"
Sub CATMain()
Dim hybridBody1 As HybridBody
Dim HybridShapeUnfold1 As HybridShapeUnfold
Dim hybridShapeFactory1 As HybridShapeFactory
Dim bodies1 As Bodies
'Dim body1 As Body

Set partDocument1 = CATIA.ActiveDocument

Set part1 = partDocument1.Part

Set bodies1 = part1.Bodies

Set body1 = bodies1.Item("FINAL SOLID")

Set hybridShapeFactory1 = part1.HybridShapeFactory

Set hybridBodies1 = part1.HybridBodies

Set hybridBody1 = hybridBodies1.Item("Geometrical Set.1")

Set hybridShapes1 = hybridBody1.HybridShapes
Set ref = CATIA.ActiveDocument.Selection.Item(1).Value
Set ref2 = CATIA.ActiveDocument.Selection.Item(2).Value
Set HybridShapeUnfold1 = hybridShapeFactory1.AddNewUnfold(ref, ref2)

'HybridShapeUnfold1.AddEdgeToTear (ref)
'hybridBody1.AppendHybridShape HybridShapeUnfold1
body1.InsertHybridShape HybridShapeUnfold1
part1.InWorkObject = HybridShapeUnfold1

part1.Update

End Sub

Attribute VB_Name = "Module2"
Sub CATMain()

Dim partDocument1 As PartDocument
Set partDocument1 = CATIA.ActiveDocument

Dim part1 As Part
Set part1 = partDocument1.Part

Dim hybridShapeFactory1 As HybridShapeFactory
Set hybridShapeFactory1 = part1.HybridShapeFactory

Dim bodies1 As Bodies
Set bodies1 = part1.Bodies

Dim body1 As Body
Set body1 = bodies1.Item("FINAL SOLID")

Dim shapes1 As Shapes
Set shapes1 = body1.Shapes

Dim solid1 As Solid
Set solid1 = shapes1.Item("FINAL SOLID")

Dim reference1 As Reference
Set reference1 = part1.CreateReferenceFromBRepName("RSur:(Face:(Brp:(FINAL SOLID;16);None:();Cf14:());WithPermanentBody;WithoutBuildError;WithSelectingFeatureSupport;MFBRepVersion_CXR29)", solid1)

Dim hybridShapeBoundary1 As HybridShapeBoundary
Set hybridShapeBoundary1 = hybridShapeFactory1.AddNewBoundaryOfSurface(reference1)

body1.InsertHybridShape hybridShapeBoundary1

part1.InWorkObject = hybridShapeBoundary1

part1.Update

part1.Update

End Sub

Attribute VB_Name = "SPAclass"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Function getLength(ref As Reference) As Double

Dim partDoc As PartDocument
Set partDoc = CATIA.ActiveDocument

Dim spaWorkbench As spaWorkbench
Set spaWorkbench = partDoc.GetWorkbench("SPAWorkbench")

Dim measurable As measurable
Set measurable = spaWorkbench.GetMeasurable(ref)

getLength = Round(measurable.Length)

End Function

Function getDirection(ref) As String

Dim partDoc, spa, mes, cood(2)

Set partDoc = CATIA.ActiveDocument
Set spa = partDoc.GetWorkbench("SPAWorkbench")
Set Meas = spa.GetMeasurable(ref)

On Error Resume Next
Meas.getDirection cood
If Err.Number > 0 Then
MsgBox Err.Description
getDirection = "Error"
End If
On Error GoTo 0

If cood(0) = 1 Or cood(0) = -1 Then
getDirection = "X"
ElseIf cood(1) = 1 Or cood(1) = -1 Then
getDirection = "Y"
ElseIf cood(2) = 1 Or cood(2) = -1 Then
getDirection = "Z"
End If

Set partDoc = Nothing
Set spa = Nothing
Set mes = Nothing
cood(0) = ""
cood(1) = ""
cood(2) = ""
End Function

Attribute VB_Name = "autoFillet"
Dim filletName As String

Sub CATMain()
    Dim doc As PartDocument
    Dim part1 As Part
    Dim sel ' As Selection
    Dim edgeList As Collection
    Dim shapeFactory As shapeFactory
    Dim refEdge As Reference
    Dim reference1 As Reference
    Dim fillet As ConstRadEdgeFillet
    Dim refLength As Double
    Dim userRadius As Long
    Dim edgeReference As Reference
    Dim i As Integer
    Dim count As Integer
    Dim refDir As String, itemDir As String
    Dim spa As SPAclass
    Dim sizeFilter As Boolean
    

    ' Initialize
    Set spa = New SPAclass
    Set doc = CATIA.ActiveDocument
    Set part1 = doc.Part
    Set sel = doc.Selection
    Set edgeList = New Collection

    If sel.count < 1 Then
        MsgBox "Please select a reference edge first.", vbExclamation
        Exit Sub
    End If

    userRadius = InputBox("Radius?")
    
    sizeFilter = False
    If MsgBox("Size Filter", vbYesNo) = vbYes Then sizeFilter = True

    ' Get reference edge and its length and direction
    Set refEdge = sel.Item(1).Value
    Dim filter(0)
    filter(0) = "Shape"

    status = sel.SelectElement2(filter, "Select a Feature", False)

    refLength = spa.getLength(refEdge)
    refDir = spa.getDirection(refEdge)

    CATIA.RefreshDisplay = True

    ' Search for edges
    sel.Search "Topology.CGMEdge,sel"
    CATIA.RefreshDisplay = True
    
    On Error Resume Next
    
    'filter by type
    For i = 1 To sel.count
    If TypeName(sel.Item(i).Value) = "TriDimFeatEdge" Then
      CATIA.StatusBar = TypeName(sel.Item(i).Value) & " " & i & "/" & sel.count
      sel.Remove i
    End If
    Next i
    
    i = 0

    ' Filter edges by name similarity
    For i = 1 To sel.count
        If isSimilar(refEdge.Name, sel.Item(i).Value.Name) Then
            edgeList.Add sel.Item(i).Value
        End If
        CATIA.StatusBar = "Name Filter " & i & "/" & sel.count
    Next i

    'If MsgBox("Total similar edges: " & edgeList.count, vbOKCancel) = vbCancel Then Exit Sub

    ' Filter by direction
    For i = edgeList.count To 1 Step -1
        itemDir = spa.getDirection(edgeList.Item(i))
        If itemDir <> refDir Then
            edgeList.Remove i
        End If
        CATIA.StatusBar = "Direction Filter " & i & "/" & edgeList.count
    Next i

    ' Create fillet feature
    Set shapeFactory = part1.shapeFactory
    Set reference1 = part1.CreateReferenceFromName("")
    Set fillet = shapeFactory.AddNewSolidEdgeFilletWithConstantRadius(reference1, catTangencyFilletEdgePropagation, userRadius)
    fillet.EdgePropagation = catTangencyFilletEdgePropagation

    ' Add filtered edges to fillet
    For i = 1 To edgeList.count
        count = count + 1
        CATIA.StatusBar = "Length Filter " & i & "/" & edgeList.count

        Set reference1 = edgeList(i)
        
        If sizeFilter Then
        'size filter
          If spa.getLength(reference1) = refLength Then
              fillet.AddObjectToFillet reference1
          End If
          
        Else
            fillet.AddObjectToFillet reference1
        End If

        part1.UpdateObject fillet
        If Err.Number > 0 Then
            fillet.WithdrawObjectToFillet reference1
        End If
        Err.Clear
    Next i

    sel.Clear
    part1.Update
End Sub

Function isSimilar(str1 As String, str2 As String) As Boolean
    Dim len1 As Integer, len2 As Integer
    Dim maxLen As Integer, minLen As Integer
    Dim threshold As Integer
    Dim distance As Integer

    len1 = Len(str1)
    len2 = Len(str2)
    maxLen = IIf(len1 > len2, len1, len2)
    minLen = IIf(len1 < len2, len1, len2)

    threshold = VBA.Round(0.98 * minLen, 0)
    distance = LevenshteinDistance(str1, str2)

    isSimilar = (distance <= threshold)
End Function

Function LevenshteinDistance(str1 As String, str2 As String) As Integer
    Dim len1 As Integer, len2 As Integer
    Dim d() As Integer
    Dim i As Integer, j As Integer
    Dim cost As Integer
    Dim X, Y, Z

    len1 = Len(str1)
    len2 = Len(str2)

    ReDim d(0 To len1, 0 To len2)
    For i = 0 To len1: d(i, 0) = i: Next i
    For j = 0 To len2: d(0, j) = j: Next j

    For j = 1 To len2
        For i = 1 To len1
            If Mid(str1, i, 1) = Mid(str2, j, 1) Then
                cost = 0
            Else
                cost = 1
            End If
            X = d(i - 1, j) + 1
            Y = d(i, j - 1) + 1
            Z = d(i - 1, j - 1) + cost
            d(i, j) = IIf(X < Y, IIf(X < Z, X, Z), IIf(Y < Z, Y, Z))
        Next i
    Next j

    LevenshteinDistance = d(len1, len2)
End Function

Attribute VB_Name = "patterninsketch"
Sub CATMain()

Dim documents1 As Documents
Set documents1 = CATIA.Documents

Dim partDocument1 As PartDocument
Set partDocument1 = documents1.Item("AIR_VENT_HOLE.CATPart")

Dim part1 As Part
Set part1 = partDocument1.Part

Dim hybridBodies1 As HybridBodies
Set hybridBodies1 = part1.HybridBodies

Dim hybridBody1 As HybridBody

Set hybridBody1 = hybridBodies1.Item(part1.InWorkObject)

Dim sketches1 As Sketches
Set sketches1 = hybridBody1.HybridSketches

Dim sketch1 As Sketch
Set sketch1 = sketches1.Item("pos")

Dim constraints1 As Constraints
Set constraints1 = sketch1.Constraints

'Dim constraint1 As Constraint
'Set constraint1 = constraints1.Item("Offset.25")

'Dim length1 As Length
'Set length1 = constraint1.Dimension

'length1.Value = 50#

Dim geometricElements1 As GeometricElements
Set geometricElements1 = sketch1.GeometricElements

Dim axis2D1 As Axis2D
Set axis2D1 = geometricElements1.Item("AbsoluteAxis")

Dim line2D1 As Line2D
Set line2D1 = axis2D1.GetItem("HDirection")

line2D1.ReportName = 1

Dim line2D2 As Line2D
Set line2D2 = axis2D1.GetItem("VDirection")

line2D2.ReportName = 2

Dim factory2D1 As Factory2D
Set factory2D1 = sketch1.Factory2D

Dim point2D1 As Point2D
Set point2D1 = factory2D1.CreatePoint(-53.684509, -181.640289)

point2D1.ReportName = 3

Dim point2D2 As Point2D
Set point2D2 = factory2D1.CreatePoint(-53.684509, 265.895996)

point2D2.ReportName = 4

Dim line2D3 As Line2D
Set line2D3 = factory2D1.CreateLine(-53.684509, -181.640289, -53.684509, 265.895996)

line2D3.ReportName = 5

line2D3.StartPoint = point2D1

line2D3.EndPoint = point2D2

Dim point2D3 As Point2D
Set point2D3 = factory2D1.CreatePoint(-103.684509, -181.640289)

point2D3.ReportName = 6

Dim point2D4 As Point2D
Set point2D4 = factory2D1.CreatePoint(-103.684509, 258.618958)

point2D4.ReportName = 7

Dim line2D4 As Line2D
Set line2D4 = factory2D1.CreateLine(-103.684509, -181.640289, -103.684509, 258.618958)

line2D4.ReportName = 8

line2D4.StartPoint = point2D3

line2D4.EndPoint = point2D4

Dim reference1 As Reference
Set reference1 = part1.CreateReferenceFromObject(line2D3)

Dim reference2 As Reference
Set reference2 = part1.CreateReferenceFromObject(line2D2)

Dim constraint2 As Constraint
Set constraint2 = constraints1.AddBiEltCst(catCstTypeVerticality, reference1, reference2)

constraint2.Mode = catCstModeDrivingDimension

Dim reference3 As Reference
Set reference3 = part1.CreateReferenceFromObject(line2D4)

Dim reference4 As Reference
Set reference4 = part1.CreateReferenceFromObject(line2D2)

Dim constraint3 As Constraint
Set constraint3 = constraints1.AddBiEltCst(catCstTypeVerticality, reference3, reference4)

constraint3.Mode = catCstModeDrivingDimension

Dim reference5 As Reference
Set reference5 = part1.CreateReferenceFromObject(line2D3)

Dim reference6 As Reference
Set reference6 = part1.CreateReferenceFromObject(line2D4)

Set constraint1 = constraints1.AddBiEltCst(catCstTypeDistance, reference5, reference6)

constraint1.Mode = catCstModeDrivingDimension

length1.Value = 50#

'---------------------------------------------------------------------------

sketch1.CloseEdition

part1.InWorkObject = hybridBody1

part1.Update

End Sub
