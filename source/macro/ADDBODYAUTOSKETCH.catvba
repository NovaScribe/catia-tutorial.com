Attribute VB_Name = "Module1"
Sub CATMain()

Dim specsAndGeomWindow1 As SpecsAndGeomWindow
Set specsAndGeomWindow1 = CATIA.ActiveWindow

Dim viewer3D1 As Viewer3D
Set viewer3D1 = specsAndGeomWindow1.ActiveViewer

Dim viewpoint3D1 As Viewpoint3D
Set viewpoint3D1 = viewer3D1.Viewpoint3D

Dim partDocument1 As PartDocument
Set partDocument1 = CATIA.ActiveDocument

Dim part1 As Part
Set part1 = partDocument1.Part

Dim bodies1 As Bodies
Set bodies1 = part1.Bodies

Dim body1 As Body
Set body1 = bodies1.Item("UPR ADD_#08032025171457")

Dim sketches1 As Sketches
Set sketches1 = body1.Sketches

Dim reference1 As Reference
Set reference1 = part1.CreateReferenceFromName("Selection_RSur:(Face:(Brp:(MEVHN65-30_3;23);None:();Cf14:());MEVHN65-30_3;Z0;G10555)")

Dim sketch1 As Sketch
Set sketch1 = sketches1.Add(reference1)

Dim arrayOfVariantOfDouble1(8)
arrayOfVariantOfDouble1(0) = 0#
arrayOfVariantOfDouble1(1) = 0#
arrayOfVariantOfDouble1(2) = 110.79
arrayOfVariantOfDouble1(3) = 1#
arrayOfVariantOfDouble1(4) = 0#
arrayOfVariantOfDouble1(5) = 0#
arrayOfVariantOfDouble1(6) = 0#
arrayOfVariantOfDouble1(7) = 1#
arrayOfVariantOfDouble1(8) = 0#
Set sketch1Variant = sketch1
sketch1Variant.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As Axis2D
Set axis2D1 = geometricElements1.Item("AbsoluteAxis")

Dim line2D1 As Line2D
Set line2D1 = axis2D1.GetItem("HDirection")

line2D1.ReportName = 1

Dim line2D2 As Line2D
Set line2D2 = axis2D1.GetItem("VDirection")

line2D2.ReportName = 2

Dim point2D1 As Point2D
Set point2D1 = factory2D1.CreatePoint(-292.88, 75#)

point2D1.ReportName = 3

Dim point2D2 As Point2D
Set point2D2 = factory2D1.CreatePoint(47.12, 75#)

point2D2.ReportName = 4

Dim line2D3 As Line2D
Set line2D3 = factory2D1.CreateLine(-292.88, 75#, 47.12, 75#)

line2D3.ReportName = 5

line2D3.StartPoint = point2D1

line2D3.EndPoint = point2D2

Dim point2D3 As Point2D
Set point2D3 = factory2D1.CreatePoint(47.12, -10#)

point2D3.ReportName = 6

Dim line2D4 As Line2D
Set line2D4 = factory2D1.CreateLine(47.12, 75#, 47.12, -10#)

line2D4.ReportName = 7

line2D4.EndPoint = point2D2

line2D4.StartPoint = point2D3

Dim point2D4 As Point2D
Set point2D4 = factory2D1.CreatePoint(-292.88, -10#)

point2D4.ReportName = 8

Dim line2D5 As Line2D
Set line2D5 = factory2D1.CreateLine(47.12, -10#, -292.88, -10#)

line2D5.ReportName = 9

line2D5.StartPoint = point2D3

line2D5.EndPoint = point2D4

Dim line2D6 As Line2D
Set line2D6 = factory2D1.CreateLine(-292.88, -10#, -292.88, 75#)

line2D6.ReportName = 10

line2D6.EndPoint = point2D4

line2D6.StartPoint = point2D1

Dim body2 As Body
Set body2 = bodies1.Item("MEVHN65-30_3")

Dim shapes1 As Shapes
Set shapes1 = body2.Shapes

Dim solid1 As Solid
Set solid1 = shapes1.Item("MEVHN65-30_3")

Dim reference2 As Reference
Set reference2 = part1.CreateReferenceFromBRepName("FEdge:(Edge:(Face:(Brp:(MEVHN65-30_3;23);None:();Cf14:());Face:(Brp:(MEVHN65-30_3;58);None:();Cf14:());None:(Limits1:();Limits2:());Cf14:());WithPermanentBody;WithoutBuildError;WithInitialFeatureSupport;MonoFond;MFBRepVersion_CXR29)", solid1)

Dim geometricElements2 As GeometricElements
Set geometricElements2 = factory2D1.CreateProjections(reference2)

Dim geometry2D1 As Geometry2D
Set geometry2D1 = geometricElements2.Item("Mark.1")

geometry2D1.Construction = True

Dim reference3 As Reference
Set reference3 = part1.CreateReferenceFromBRepName("FEdge:(Edge:(Face:(Brp:(MEVHN65-30_3;23);None:();Cf14:());Face:(Brp:(MEVHN65-30_3;54);None:();Cf14:());None:(Limits1:();Limits2:());Cf14:());WithPermanentBody;WithoutBuildError;WithInitialFeatureSupport;MonoFond;MFBRepVersion_CXR29)", solid1)

Dim geometricElements3 As GeometricElements
Set geometricElements3 = factory2D1.CreateProjections(reference3)

Dim geometry2D2 As Geometry2D
Set geometry2D2 = geometricElements3.Item("Mark.1")

geometry2D2.Construction = True

Dim reference4 As Reference
Set reference4 = part1.CreateReferenceFromBRepName("FEdge:(Edge:(Face:(Brp:(MEVHN65-30_3;107);None:();Cf14:());Face:(Brp:(MEVHN65-30_3;62);None:();Cf14:());None:(Limits1:();Limits2:());Cf14:());WithPermanentBody;WithoutBuildError;WithInitialFeatureSupport;MonoFond;MFBRepVersion_CXR29)", solid1)

Dim geometricElements4 As GeometricElements
Set geometricElements4 = factory2D1.CreateProjections(reference4)

Dim geometry2D3 As Geometry2D
Set geometry2D3 = geometricElements4.Item("Mark.1")

geometry2D3.Construction = True

Dim reference5 As Reference
Set reference5 = part1.CreateReferenceFromBRepName("FEdge:(Edge:(Face:(Brp:(MEVHN65-30_3;23);None:();Cf14:());Face:(Brp:(MEVHN65-30_3;55);None:();Cf14:());None:(Limits1:();Limits2:());Cf14:());WithPermanentBody;WithoutBuildError;WithInitialFeatureSupport;MonoFond;MFBRepVersion_CXR29)", solid1)

Dim geometricElements5 As GeometricElements
Set geometricElements5 = factory2D1.CreateProjections(reference5)

Dim geometry2D4 As Geometry2D
Set geometry2D4 = geometricElements5.Item("Mark.1")

geometry2D4.Construction = True

Dim constraints1 As Constraints
Set constraints1 = sketch1.Constraints

Dim reference6 As Reference
Set reference6 = part1.CreateReferenceFromObject(line2D3)

Dim reference7 As Reference
Set reference7 = part1.CreateReferenceFromObject(line2D1)

Dim constraint1 As Constraint
Set constraint1 = constraints1.AddBiEltCst(catCstTypeHorizontality, reference6, reference7)

constraint1.Mode = catCstModeDrivingDimension

Dim reference8 As Reference
Set reference8 = part1.CreateReferenceFromObject(line2D5)

Dim reference9 As Reference
Set reference9 = part1.CreateReferenceFromObject(line2D1)

Dim constraint2 As Constraint
Set constraint2 = constraints1.AddBiEltCst(catCstTypeHorizontality, reference8, reference9)

constraint2.Mode = catCstModeDrivingDimension

Dim reference10 As Reference
Set reference10 = part1.CreateReferenceFromObject(line2D4)

Dim reference11 As Reference
Set reference11 = part1.CreateReferenceFromObject(line2D2)

Dim constraint3 As Constraint
Set constraint3 = constraints1.AddBiEltCst(catCstTypeVerticality, reference10, reference11)

constraint3.Mode = catCstModeDrivingDimension

Dim reference12 As Reference
Set reference12 = part1.CreateReferenceFromObject(line2D6)

Dim reference13 As Reference
Set reference13 = part1.CreateReferenceFromObject(line2D2)

Dim constraint4 As Constraint
Set constraint4 = constraints1.AddBiEltCst(catCstTypeVerticality, reference12, reference13)

constraint4.Mode = catCstModeDrivingDimension

Dim reference14 As Reference
Set reference14 = part1.CreateReferenceFromObject(geometry2D1)

Dim reference15 As Reference
Set reference15 = part1.CreateReferenceFromObject(line2D4)

Dim constraint5 As Constraint
Set constraint5 = constraints1.AddBiEltCst(catCstTypeDistance, reference14, reference15)

constraint5.Mode = catCstModeDrivingDimension

Dim length1 As Length
Set length1 = constraint5.Dimension

length1.Value = 10#

Dim reference16 As Reference
Set reference16 = part1.CreateReferenceFromObject(geometry2D2)

Dim reference17 As Reference
Set reference17 = part1.CreateReferenceFromObject(line2D3)

Dim constraint6 As Constraint
Set constraint6 = constraints1.AddBiEltCst(catCstTypeDistance, reference16, reference17)

constraint6.Mode = catCstModeDrivingDimension

Dim length2 As Length
Set length2 = constraint6.Dimension

length2.Value = 10#

Dim reference18 As Reference
Set reference18 = part1.CreateReferenceFromObject(geometry2D3)

Dim reference19 As Reference
Set reference19 = part1.CreateReferenceFromObject(line2D6)

Dim constraint7 As Constraint
Set constraint7 = constraints1.AddBiEltCst(catCstTypeDistance, reference18, reference19)

constraint7.Mode = catCstModeDrivingDimension

Dim length3 As Length
Set length3 = constraint7.Dimension

length3.Value = 40#

Dim reference20 As Reference
Set reference20 = part1.CreateReferenceFromObject(geometry2D4)

Dim reference21 As Reference
Set reference21 = part1.CreateReferenceFromObject(line2D5)

Dim constraint8 As Constraint
Set constraint8 = constraints1.AddBiEltCst(catCstTypeDistance, reference20, reference21)

constraint8.Mode = catCstModeDrivingDimension

Dim length4 As Length
Set length4 = constraint8.Dimension

length4.Value = 10#

sketch1.CloseEdition

part1.InWorkObject = body1

part1.Update

length1.Value = 10#

length2.Value = 10#

length3.Value = 40#

length4.Value = 10#

part1.InWorkObject = body1

Dim shapeFactory1 As ShapeFactory
Set shapeFactory1 = part1.ShapeFactory

Dim pad1 As Pad
Set pad1 = shapeFactory1.AddNewPad(sketch1, 15#)

Dim limit1 As Limit
Set limit1 = pad1.FirstLimit

Dim length5 As Length
Set length5 = limit1.Dimension

length5.Value = 50#

part1.Update

Dim reference22 As Reference
Set reference22 = part1.CreateReferenceFromName("Selection_RSur:(Face:(Brp:(Pad.3;1);None:();Cf14:());Pad.3_ResultOUT;Z0;G10555)")

Dim sketch2 As Sketch
Set sketch2 = sketches1.Add(reference22)

Dim arrayOfVariantOfDouble2(8)
arrayOfVariantOfDouble2(0) = 0#
arrayOfVariantOfDouble2(1) = 0#
arrayOfVariantOfDouble2(2) = 110.79
arrayOfVariantOfDouble2(3) = 1#
arrayOfVariantOfDouble2(4) = 0#
arrayOfVariantOfDouble2(5) = 0#
arrayOfVariantOfDouble2(6) = 0#
arrayOfVariantOfDouble2(7) = -1#
arrayOfVariantOfDouble2(8) = 0#
Set sketch2Variant = sketch2
sketch2Variant.SetAbsoluteAxisData arrayOfVariantOfDouble2

part1.InWorkObject = sketch2

Dim factory2D2 As Factory2D
Set factory2D2 = sketch2.OpenEdition()

Dim geometricElements6 As GeometricElements
Set geometricElements6 = sketch2.GeometricElements

Dim axis2D2 As Axis2D
Set axis2D2 = geometricElements6.Item("AbsoluteAxis")

Dim line2D7 As Line2D
Set line2D7 = axis2D2.GetItem("HDirection")

line2D7.ReportName = 1

Dim line2D8 As Line2D
Set line2D8 = axis2D2.GetItem("VDirection")

line2D8.ReportName = 2

Dim point2D5 As Point2D
Set point2D5 = factory2D2.CreatePoint(-292.88, -75#)

point2D5.ReportName = 3

Dim reference23 As Reference
Set reference23 = part1.CreateReferenceFromBRepName("FVertex:(Vertex:(Non Ordered Neighbours:(Face:(Brp:(Pad.3;0:(Brp:(Sketch.4;5)));None:();Cf14:());Face:(Brp:(Pad.3;0:(Brp:(Sketch.4;10)));None:();Cf14:());Face:(Brp:(Pad.3;1);None:();Cf14:()));Cf14:());WithPermanentBody;WithoutBuildError;WithInitialFeatureSupport;MonoFond;MFBRepVersion_CXR29)", pad1)

Dim geometricElements7 As GeometricElements
Set geometricElements7 = factory2D2.CreateProjections(reference23)

Dim geometry2D5 As Geometry2D
Set geometry2D5 = geometricElements7.Item("Mark.1")

geometry2D5.Construction = True

Dim point2D6 As Point2D
Set point2D6 = factory2D2.CreatePoint(-252.88, -75#)

point2D6.ReportName = 4

Dim line2D9 As Line2D
Set line2D9 = factory2D2.CreateLine(-292.88, -75#, -252.88, -75#)

line2D9.ReportName = 5

line2D9.StartPoint = point2D5

line2D9.EndPoint = point2D6

Dim point2D7 As Point2D
Set point2D7 = factory2D2.CreatePoint(-252.88, 10#)

point2D7.ReportName = 6

Dim line2D10 As Line2D
Set line2D10 = factory2D2.CreateLine(-252.88, -75#, -252.88, 10#)

line2D10.ReportName = 7

line2D10.StartPoint = point2D6

line2D10.EndPoint = point2D7

Dim point2D8 As Point2D
Set point2D8 = factory2D2.CreatePoint(-292.88, 10#)

point2D8.ReportName = 8

Dim line2D11 As Line2D
Set line2D11 = factory2D2.CreateLine(-252.88, 10#, -292.88, 10#)

line2D11.ReportName = 9

line2D11.StartPoint = point2D7

line2D11.EndPoint = point2D8

Dim line2D12 As Line2D
Set line2D12 = factory2D2.CreateLine(-292.88, 10#, -292.88, -75#)

line2D12.ReportName = 10

line2D12.StartPoint = point2D8

line2D12.EndPoint = point2D5

Dim reference24 As Reference
Set reference24 = part1.CreateReferenceFromBRepName("FEdge:(Edge:(Face:(Brp:(Pad.3;1);None:();Cf14:());Face:(Brp:(Pad.3;0:(Brp:(Sketch.4;9)));None:();Cf14:());None:(Limits1:();Limits2:());Cf14:());WithPermanentBody;WithoutBuildError;WithInitialFeatureSupport;MonoFond;MFBRepVersion_CXR29)", pad1)

Dim geometricElements8 As GeometricElements
Set geometricElements8 = factory2D2.CreateProjections(reference24)

Dim geometry2D6 As Geometry2D
Set geometry2D6 = geometricElements8.Item("Mark.1")

geometry2D6.Construction = True

Dim reference25 As Reference
Set reference25 = part1.CreateReferenceFromBRepName("FSur:(Face:(Brp:(MEVHN65-30_3;107);None:();Cf14:());WithPermanentBody;WithoutBuildError;WithInitialFeatureSupport;MonoFond;MFBRepVersion_CXR29)", solid1)

Dim geometricElements9 As GeometricElements
Set geometricElements9 = factory2D2.CreateIntersections(reference25)

Dim geometry2D7 As Geometry2D
Set geometry2D7 = geometricElements9.Item("Mark.1")

geometry2D7.Construction = True

Dim constraints2 As Constraints
Set constraints2 = sketch2.Constraints

Dim reference26 As Reference
Set reference26 = part1.CreateReferenceFromObject(point2D5)

Dim reference27 As Reference
Set reference27 = part1.CreateReferenceFromObject(geometry2D5)

Dim constraint9 As Constraint
Set constraint9 = constraints2.AddBiEltCst(catCstTypeOn, reference26, reference27)

constraint9.Mode = catCstModeDrivingDimension

Dim reference28 As Reference
Set reference28 = part1.CreateReferenceFromObject(line2D9)

Dim reference29 As Reference
Set reference29 = part1.CreateReferenceFromObject(line2D7)

Dim constraint10 As Constraint
Set constraint10 = constraints2.AddBiEltCst(catCstTypeHorizontality, reference28, reference29)

constraint10.Mode = catCstModeDrivingDimension

Dim reference30 As Reference
Set reference30 = part1.CreateReferenceFromObject(line2D11)

Dim reference31 As Reference
Set reference31 = part1.CreateReferenceFromObject(line2D7)

Dim constraint11 As Constraint
Set constraint11 = constraints2.AddBiEltCst(catCstTypeHorizontality, reference30, reference31)

constraint11.Mode = catCstModeDrivingDimension

Dim reference32 As Reference
Set reference32 = part1.CreateReferenceFromObject(line2D10)

Dim reference33 As Reference
Set reference33 = part1.CreateReferenceFromObject(line2D8)

Dim constraint12 As Constraint
Set constraint12 = constraints2.AddBiEltCst(catCstTypeVerticality, reference32, reference33)

constraint12.Mode = catCstModeDrivingDimension

Dim reference34 As Reference
Set reference34 = part1.CreateReferenceFromObject(line2D12)

Dim reference35 As Reference
Set reference35 = part1.CreateReferenceFromObject(line2D8)

Dim constraint13 As Constraint
Set constraint13 = constraints2.AddBiEltCst(catCstTypeVerticality, reference34, reference35)

constraint13.Mode = catCstModeDrivingDimension

Dim reference36 As Reference
Set reference36 = part1.CreateReferenceFromObject(point2D7)

Dim reference37 As Reference
Set reference37 = part1.CreateReferenceFromObject(geometry2D6)

Dim constraint14 As Constraint
Set constraint14 = constraints2.AddBiEltCst(catCstTypeOn, reference36, reference37)

constraint14.Mode = catCstModeDrivingDimension

Dim reference38 As Reference
Set reference38 = part1.CreateReferenceFromObject(geometry2D7)

Dim reference39 As Reference
Set reference39 = part1.CreateReferenceFromObject(line2D10)

Dim constraint15 As Constraint
Set constraint15 = constraints2.AddBiEltCst(catCstTypeOn, reference38, reference39)

constraint15.Mode = catCstModeDrivingDimension

sketch2.CloseEdition

part1.InWorkObject = pad1

part1.Update

Dim pad2 As Pad
Set pad2 = shapeFactory1.AddNewPad(sketch2, 50#)

Dim limit2 As Limit
Set limit2 = pad2.FirstLimit

Dim length6 As Length
Set length6 = limit2.Dimension

length6.Value = 15#

part1.Update

length6.Value = 20#

part1.Update

Set partDocument1 = CATIA.ActiveDocument

Set partDocument1 = CATIA.ActiveDocument

Dim selection1 As Selection
Set selection1 = partDocument1.Selection

Dim visPropertySet1 As VisPropertySet
Set visPropertySet1 = selection1.VisProperties

visPropertySet1.SetRealColor 0, 0, 255, 0

Set partDocument1 = CATIA.ActiveDocument

Dim selection2 As Selection
Set selection2 = partDocument1.Selection

selection2.Clear

End Sub
