Attribute VB_Name = "Module1"
Sub CATMain()

ReDim sFilter(0)
sFilter(0) = "Edge"
sStatus = CATIA.ActiveDocument.Selection.SelectElement3(sFilter, "select a  local axis", False)
Dim axiscoord(2)

End Sub

Attribute VB_Name = "autoSelectCorner"
Sub CATMain()

Dim prtDoc As PartDocument
Dim sel As Selection

Set prtDoc = CATIA.ActiveDocument
Set sel = prtDoc.Selection


sStatus = sel.SelectElement()

sel.Search "Topology.Edge,sel"
If sel.Count <= 0 Then
Exit Sub
End If

Debug.Print sel.Count

For X = sel.Count To 1 Step -1

If isSimilar.isSimilar("Selection_REdge:(Edge:(Face:(Brp:(Pocket.89;1);None:();Cf11:());Face:(Brp:((Brp:(Pocket.95;0:(Brp:(Sketch.285;14)));Brp:(MultiPad.1;0:(Brp:(Sketch.284;(Brp:(Sketch.284_ProjectedGeomSet.11;(Brp:(FeatureRSUR.573;(Brp:(Pad.90;4:(Brp:(Sketch.283;31)));Brp:(Pad.90;2)))))))));Brp:(Pad.90;4:(Brp:(Sketch.283;31)))));None:();Cf11:());None:(Limits1:();Limits2:());Cf11:());Pocket.98_ResultOUT;Z0;G6937", sel.Item(X).Value.Name) = True Then
Debug.Print sel.Item(X).Value.Name
Else
sel.Remove X
End If
Next X
Debug.Print sel.Count
End Sub

Attribute VB_Name = "isSimilar"
Function isSimilar(str1 As String, str2 As String) As Boolean
    Dim len1 As Integer, len2 As Integer
    Dim maxLen As Integer, minLen As Integer
    Dim threshold As Integer
    Dim distance As Integer
   
    ' Calculate the length of the input strings
    len1 = Len(str1)
    len2 = Len(str2)
   
    ' Determine the maximum and minimum length
    'maxLen = WorksheetFunction.Max(len1, len2)
    If len1 < len2 Then
    maxLen = len2
    Else
    maxLen = len1
    End If
    
    'minLen = WorksheetFunction.Min(len1, len2)
    
   If len1 > len2 Then
    minLen = len1
    Else
    minLen = len2
    End If
    
    ' Define the threshold based on the length of the strings
    threshold = Round(0.3 * minLen, 0)
   
    ' Calculate the Levenshtein distance between the strings
    distance = LevenshteinDistance(str1, str2)
   
    ' Determine if the distance is within the threshold
    If distance <= threshold Then
        isSimilar = True
    Else
        isSimilar = False
    End If
End Function

Function LevenshteinDistance(str1 As String, str2 As String) As Integer
    Dim len1 As Integer, len2 As Integer
    Dim d() As Integer
    Dim i As Integer, j As Integer
    Dim cost As Integer
   
    ' Calculate the length of the input strings
    len1 = Len(str1)
    len2 = Len(str2)
   
    ' Initialize the distance matrix
    ReDim d(0 To len1, 0 To len2)
    For i = 0 To len1
        d(i, 0) = i
    Next i
    For j = 0 To len2
        d(0, j) = j
    Next j
   
    ' Compute the edit distance
    For j = 1 To len2
        For i = 1 To len1
            If Mid(str1, i, 1) = Mid(str2, j, 1) Then
                cost = 0
            Else
                cost = 1
            End If
            s1 = d(i - 1, j) + 1  '10
            s2 = d(i, j - 1) + 1  '20
            s3 = d(i - 1, j - 1) + cost  '15

'd(i, j) = WorksheetFunction.Min(d(i - 1, j) + 1, d(i, j - 1) + 1, d(i - 1, j - 1) + cost)

If s1 <= s2 And s1 <= s3 Then
d(i, j) = s1
ElseIf s2 <= s1 And s2 <= s3 Then
d(i, j) = s2
ElseIf s3 <= s1 And s3 <= s2 Then
d(i, j) = s3
Else
MsgBox s1 & "  " & s2 & "  " & s3
End If
        Next i
    Next j
   
    ' Return the Levenshtein distance
    LevenshteinDistance = d(len1, len2)
End Function
