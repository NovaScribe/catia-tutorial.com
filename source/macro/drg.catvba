Attribute VB_Name = "Module1"
Sub CATMain()
On Error GoTo errorHandle:

Dim drawingDocument1 As DrawingDocument
Set drawingDocument1 = CATIA.ActiveDocument

Dim drawingSheets1 As DrawingSheets
Set drawingSheets1 = drawingDocument1.Sheets

Dim drawingSheet1 As DrawingSheet
Set drawingSheet1 = drawingSheets1.Item(1)

Dim drawingViews1 'As DrawingViews
Set drawingViews1 = drawingSheet1.Views

Dim drawingView1 'As DrawingView
Set drawingView1 = drawingViews1.Item(3)

If drawingView1.Dimensions.Count = 0 Then
MsgBox "Dimension Not Found"
Exit Sub
End If

'catDimDistance = 0
'catDimDistanceOffset = 1
'catDimLength = 2
'catDimLengthCurvilinear = 3
'catDimAngle = 4
'catDimRadius = 5
'catDimRadiusTangent = 6
'catDimRadiusCylinder = 7
'catDimRadiusEdge = 8
'catDimDiameter = 9
'catDimDiameterTangent = 10
'catDimDiameterCylinder = 11
'catDimDiameterEdge = 12
'catDimDiameterCone = 13
'catDimChamfer = 14
'catDimSlope = 15
'catDimLengthCircular = 16 (&H10)
'catDimRadiusFillet = 17 (&H11)
'catDimDiameterTorus = 18 (&H12)
'catDimRadiusTorus = 19 (&H13)
'catDimDistanceMin = 20 (&H14)

Dim dimD As DrawingDimension
Dim dimL As DrawingDimValue

For i = 1 To drawingView1.Dimensions.Count

    
    Set dimL = drawingView1.Dimensions.Item(i).GetValue()
    Set dimD = drawingView1.Dimensions.Item(i)
    
    If dimD.DimType = catDimDistance Or dimD.DimType = catDimLength Then
    'set Precision
    dimL.SetFormatPrecision 1, 0.01
    
    'set perfix surfix
    dimL.SetPSText 1, "", ""
    
    ' Display format
    dimL.SetFormatName 1, "ANS.DIMM"
    
    End If
    
    'Dim dimTypeDetails As String
    'grade = Switch(dimD.DimType = 0, "catDimDistance", score >= 80, "B", score >= 70, "C")
    
    'Debug.Print dimL.Value & "-----" & dimD.DimType
    
    If dimD.DimType = catDimDiameter Then
    'dimL.SetPSText 1, "Ø", ""
    ElseIf dimD.DimType = catDimRadius Then
    'dimL.SetPSText 1, "R", ""
    End If
    
    
Next i

Exit Sub

errorHandle:
Debug.Print Err.Description
MsgBox "Error Occur : " & Err.Description, vbInformation

End Sub
